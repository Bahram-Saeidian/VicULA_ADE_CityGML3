FME workspace Conversion_pipeline.fmw

Parameters:
- SourceDataset_SHAPEFILE = $(FME_MF_DIR)Sewerage_Network_Main_Pipelines-shp\85e6e9e4-1bec-48b9-8982-253ed749a2a7202041-1-1obtgd5.s962.shp   # Source Esri Shapefile(s)
- SourceDataset_SQLITE3FDO_5 = $(FME_MF_DIR)Case study 2\1377176\Case study 2.sqlite   # SQLite3 Spatial (FDO) Database
- SourceDataset_SHAPEFILE_9 = D:\Implementation\CityGML\Demonstration\Case study 1\Shapefiles\Drainage\Pipelines_properties.shp   # Source Esri Shapefile(s)
- SourceDataset_SHAPEFILE_7 = D:\Implementation\CityGML\Demonstration\Case study 1\Shapefiles\Parcel\Parcel_properties.shp   # Source Esri Shapefile(s)
- SourceDataset_FBX_9 = D:\Implementation\CityGML\Demonstration\Case study 1\3D Model of Physical Assets\buildings.fbx   # Source FBX File(s)
- SourceDataset_FBX_11 = D:\Implementation\CityGML\Demonstration\Case study 1\3D Model of Physical Assets\ground.fbx   # Source FBX File(s)
- SourceDataset_FBX_7 = D:\Implementation\CityGML\Demonstration\Case study 1\3D Model of Physical Assets\roads.fbx   # Source FBX File(s)
- SourceDataset_FBX = D:\Implementation\CityGML\Demonstration\Case study 1\3D Model of Physical Assets\pipelines.fbx   # Source FBX File(s)
- SourceDataset_FBX_6 = D:\Implementation\CityGML\Demonstration\Case study 1\3D Model of Physical Assets\tunnels.fbx   # Source FBX File(s)
- SourceDataset_FFS = D:\Implementation\CityGML\Demonstration\Case study 1\3D Model of Legal Spaces\3DLegalSpaces.ffs   # Source FME Feature Store (FFS) File(s)
- DestDataset_GML = VicULA_test_CityGML3   # Destination Geography Markup Language (GML) File

Readers:
- SHAPEFILE_1: SHAPEFILE from $(SourceDataset_SHAPEFILE)
- SQLITE3FDO_2: SQLITE3FDO from $(SourceDataset_SQLITE3FDO_5)
- SHAPEFILE_2: SHAPEFILE from $(SourceDataset_SHAPEFILE_9)
- SHAPEFILE_3: SHAPEFILE from $(SourceDataset_SHAPEFILE_7)
- FBX_1: FBX from $(SourceDataset_FBX)
- FBX_2: FBX from $(SourceDataset_FBX_9)
- FBX_3: FBX from $(SourceDataset_FBX_11)
- FBX_4: FBX from $(SourceDataset_FBX_7)
- FBX_5: FBX from $(SourceDataset_FBX_6)
- FFS_1: FFS from $(SourceDataset_FFS)

Writers:
- GML_1: GML to $(DestDataset_GML)

ground (reader FBX_3)
    -> Deaggregator_1
Deaggregator_1
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryFilter_1
GeometryFilter_1
    FILTER_MODE = SIMPLE
    FILTER_MULTI = FILTER_TYPES]Surface]FME_CONTROLLER_QUERY_FILE]]FME_CONTROLLER_CHOICE]Simple
    Surface -> GeometryExtractor_1
GeometryExtractor_1
    ATTR = extent
    GENERATE_GEOMETRY_IDS = No
    KIND_LONG = GML v3.2.1
    OMIT_NAMESPACES_DISPLAY = No
    PREFER_POLYGON_OVER_SURFACE = No
    REMOVE_GEOMETRY = No
    -> AttributeCreator_2
AttributeCreator_2
    ATTR_TABLE = SET_TO citygml_lod_name = @Value(extent)
    -> GeometryPropertySetter
pipelines (reader FBX_1)
    -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> FeatureMerger_1 [REQUESTOR]
Pipelines_properties (reader SHAPEFILE_2)
    attributes: built varchar(254), carrying varchar(254), condition varchar(254), diameter varchar(254), dnstr_inv varchar(254), dnstr_pit varchar(254), form varchar(254), height_mm varchar(254), mat_desc varchar(254), material varchar(254), operator varchar(254), ref varchar(254), upstr_inv varchar(254), upstr_pit varchar(254), width_mm varchar(254), Shape_Leng double, ObjectID varchar(254)
    -> FeatureMerger_1 [SUPPLIER]
FeatureMerger_1
    ATTR_ACCUM_MODE = Merge Supplier
    ATTR_CONFLICT_RES = Use Requestor
    IGNORE_NULLS = No
    JOIN_KEYS = @Value(_geometry_name) @Value(ObjectID) AUTO
    MERGE_TYPE = Attributes Only
    PROCESS_DUPS = NO
    REJECT_NULL_MISSING_KEYS = No
    SUPPLIERS_FIRST = No
    MERGED -> GeometryFilter_2
buildings (reader FBX_2)
    -> Deaggregator_3
tunnels (reader FBX_5)
    -> Deaggregator_3
roads (reader FBX_4)
    -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryFilter_2
GeometryFilter_2
    FILTER_MODE = SIMPLE
    FILTER_MULTI = FILTER_TYPES]Surface]FME_CONTROLLER_QUERY_FILE]]FME_CONTROLLER_CHOICE]Simple
    Surface -> GeometryExtractor_2
3DLegalSpaces (reader FFS_1)
    attributes: PARCEL_PFI varchar(10), PARCEL_SPI varchar(18), PC_SPIC int32, PC_DTYPE varchar(2), PC_LGAC varchar(3), PC_PLANNO varchar(9), PC_LOTNO varchar(12), PARC_ACCLT varchar(1), PC_ALL varchar(10), PARCEL_SEC varchar(12), PC_BLK varchar(12), PC_PORT varchar(12), PC_SUB varchar(12), PC_CRSTAT varchar(1), PC_PARC varchar(4), PC_TOWNC varchar(5), PC_PNUM varchar(10), PC_FDESC varchar(80), PC_PART varchar(1), PC_CREFNO varchar(15), PC_STAT varchar(1), PC_PFI_CR date, PARCEL_UFI int32, PC_UFI_CR date, PC_UFI_OL int32, PARV_PFI varchar(10), PV_CNT_PFI varchar(10), ZLEVEL varchar(2), PV_PFI_CR date, PARV_UFI int32,
      PV_UFI_CR date, PV_UFI_OLD int32, Shape_Leng real64, Shape_Le_1 real64, Shape_Le_2 real64, LegalSpace varchar(254), ParcelDime varchar(254), ParcelName varchar(254), ParcelStat varchar(254), ParcelTitl varchar(254), ParcelType varchar(254), ParcelUse varchar(254), Lot_Entitl varchar(254), Lot_Liabil varchar(254), Lot_Owner varchar(254), Lot_TitleR varchar(254), Lot_Titl_1 varchar(254), CM_OCType varchar(254), EA_Benefic varchar(254), EA_Easemen varchar(254), EA_Origin varchar(254), EA_Width varchar(254), DL_LandApp varchar(254), DL_Length varchar(254), DL_LowerLi varchar(254), DL_UpperLi varchar(254), Shape_Le_3 real64, Shape_Area real64, _part_number uint64, _geometry_name buffer,
      Volume real64
    -> GeometryExtractor_2
GeometryExtractor_2
    ATTR = lod3MultiSurface
    GENERATE_GEOMETRY_IDS = No
    KIND_LONG = GML v3.2.1
    OMIT_NAMESPACES_DISPLAY = No
    PREFER_POLYGON_OVER_SURFACE = No
    REMOVE_GEOMETRY = No
    -> AttributeCreator_3
AttributeCreator_3
    ATTR_TABLE = SET_TO citygml_lod_name = @Value(lod3MultiSurface)
    -> GeometryPropertySetter
GeometryPropertySetter
    OVERWRITE_CHOICE = Yes
    REMOVE_ATTRIBUTE = No
    SETTYPE_PARAM = Traits From Attributes
    SRC_ATTRS = citygml_lod_name
    SET -> FeatureMerger_2 [REQUESTOR]
Creator
    GEOMTYPE = Geometry Object
    NUM = 1
    CREATED -> AttributeCreator_1
AttributeCreator_1
    ATTR_TABLE:
      SET_TO gml_name{0} = VicULA test
      SET_TO gml_description = This is a test!
      SET_TO gml_id = id_@UUID()
    -> AttributeRenamer
    -> CityModel (writer GML_1)
CityModel (writer GML_1)
    attributes: adeOfAbstractFeature{} xml_xml, creationDate xml_datetime, terminationDate xml_datetime, validFrom xml_datetime, validTo xml_datetime, adeOfAbstractFeatureWithLifespan{} xml_xml, engineeringCRS xml_xml, engineeringCRS.nilReason xml_buffer, engineeringCRS.gml_remoteSchema xml_buffer, engineeringCRS.xlink_href xml_buffer, engineeringCRS.xlink_role xml_buffer, engineeringCRS.xlink_title xml_buffer, engineeringCRS.owns xml_boolean, cityObjectMember{}.nilReason xml_buffer, cityObjectMember{}.gml_remoteSchema xml_buffer, cityObjectMember{}.xlink_href xml_buffer, cityObjectMember{}.xlink_role xml_buffer, cityObjectMember{}.xlink_title xml_buffer, cityObjectMember{}.owns xml_boolean, appearanceMember{}.nilReason xml_buffer, appearanceMember{}.gml_remoteSchema xml_buffer, appearanceMember{}.xlink_href xml_buffer, appearanceMember{}.xlink_role xml_buffer, appearanceMember{}.xlink_title xml_buffer, appearanceMember{}.owns xml_boolean, versionMember{}.nilReason xml_buffer, versionMember{}.gml_remoteSchema xml_buffer, versionMember{}.xlink_href xml_buffer, versionMember{}.xlink_role xml_buffer, versionMember{}.xlink_title xml_buffer,
      versionMember{}.owns xml_boolean, versionTransitionMember{}.nilReason xml_buffer, versionTransitionMember{}.gml_remoteSchema xml_buffer, versionTransitionMember{}.xlink_href xml_buffer, versionTransitionMember{}.xlink_role xml_buffer, versionTransitionMember{}.xlink_title xml_buffer, versionTransitionMember{}.owns xml_boolean, featureMember{}.nilReason xml_buffer, featureMember{}.gml_remoteSchema xml_buffer, featureMember{}.xlink_href xml_buffer, featureMember{}.xlink_role xml_buffer, featureMember{}.xlink_title xml_buffer, featureMember{}.owns xml_boolean, adeOfCityModel{} xml_xml
AttributeRenamer
    ATTR_TABLE = RENAME_SET_DEFAULT gml_id > gml_parent_id
    MISSING_INPUT_ATTRS = REMOVE
    -> FeatureMerger_2 [SUPPLIER]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FeatureTypeFilter
FeatureTypeFilter
    ATTRIBUTES = ground,pipelines,buildings,tunnels,roads,3DLegalSpaces,<Blank>,<Unfiltered>
    ground -> TINRelief (writer GML_1)
    pipelines -> GenericOccupiedSpace (writer GML_1)
    buildings -> Building (writer GML_1)
    tunnels -> Tunnel (writer GML_1)
    roads -> Road (writer GML_1)
    3DLegalSpaces -> AttributeFilter
TINRelief (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, adeOfAbstractSpaceBoundary{} xml_xml, lod xml_int64, extent xml_geometry, adeOfAbstractReliefComponent{} xml_xml, tin xml_geometry, adeOfTINRelief{} xml_xml
GenericOccupiedSpace (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, lod1TerrainIntersectionCurve xml_geometry, lod2TerrainIntersectionCurve xml_geometry,
      lod3TerrainIntersectionCurve xml_geometry, pointCloud.nilReason xml_buffer, pointCloud.gml_remoteSchema xml_buffer, pointCloud.xlink_href xml_buffer, pointCloud.xlink_role xml_buffer, pointCloud.xlink_title xml_buffer, pointCloud.owns xml_boolean, adeOfAbstractPhysicalSpace{} xml_xml, lod1ImplicitRepresentation.nilReason xml_buffer, lod1ImplicitRepresentation.gml_remoteSchema xml_buffer, lod1ImplicitRepresentation.xlink_href xml_buffer, lod1ImplicitRepresentation.xlink_role xml_buffer, lod1ImplicitRepresentation.xlink_title xml_buffer, lod1ImplicitRepresentation.owns xml_boolean, lod1ImplicitRepresentation.ImplicitGeometry.gml_id xml_buffer, lod1ImplicitRepresentation.ImplicitGeometry.transformationMatrix xml_buffer, lod1ImplicitRepresentation.ImplicitGeometry.mimeType xml_buffer, lod1ImplicitRepresentation.ImplicitGeometry.mimeType.codeSpace xml_buffer, lod1ImplicitRepresentation.ImplicitGeometry.libraryObject xml_buffer, lod1ImplicitRepresentation.ImplicitGeometry.referencePoint xml_geometry, lod1ImplicitRepresentation.ImplicitGeometry.relativeGeometry xml_geometry, lod1ImplicitRepresentation.ImplicitGeometry.appearance{}.nilReason xml_buffer, lod1ImplicitRepresentation.ImplicitGeometry.appearance{}.gml_remoteSchema xml_buffer, lod1ImplicitRepresentation.ImplicitGeometry.appearance{}.xlink_href xml_buffer, lod1ImplicitRepresentation.ImplicitGeometry.appearance{}.xlink_role xml_buffer, lod1ImplicitRepresentation.ImplicitGeometry.appearance{}.xlink_title xml_buffer, lod1ImplicitRepresentation.ImplicitGeometry.appearance{}.owns xml_boolean, lod2ImplicitRepresentation.nilReason xml_buffer, lod2ImplicitRepresentation.gml_remoteSchema xml_buffer, lod2ImplicitRepresentation.xlink_href xml_buffer,
      lod2ImplicitRepresentation.xlink_role xml_buffer, lod2ImplicitRepresentation.xlink_title xml_buffer, lod2ImplicitRepresentation.owns xml_boolean, lod2ImplicitRepresentation.ImplicitGeometry.gml_id xml_buffer, lod2ImplicitRepresentation.ImplicitGeometry.transformationMatrix xml_buffer, lod2ImplicitRepresentation.ImplicitGeometry.mimeType xml_buffer, lod2ImplicitRepresentation.ImplicitGeometry.mimeType.codeSpace xml_buffer, lod2ImplicitRepresentation.ImplicitGeometry.libraryObject xml_buffer, lod2ImplicitRepresentation.ImplicitGeometry.referencePoint xml_geometry, lod2ImplicitRepresentation.ImplicitGeometry.relativeGeometry xml_geometry, lod2ImplicitRepresentation.ImplicitGeometry.appearance{}.nilReason xml_buffer, lod2ImplicitRepresentation.ImplicitGeometry.appearance{}.gml_remoteSchema xml_buffer, lod2ImplicitRepresentation.ImplicitGeometry.appearance{}.xlink_href xml_buffer, lod2ImplicitRepresentation.ImplicitGeometry.appearance{}.xlink_role xml_buffer, lod2ImplicitRepresentation.ImplicitGeometry.appearance{}.xlink_title xml_buffer, lod2ImplicitRepresentation.ImplicitGeometry.appearance{}.owns xml_boolean, lod3ImplicitRepresentation.nilReason xml_buffer, lod3ImplicitRepresentation.gml_remoteSchema xml_buffer, lod3ImplicitRepresentation.xlink_href xml_buffer, lod3ImplicitRepresentation.xlink_role xml_buffer, lod3ImplicitRepresentation.xlink_title xml_buffer, lod3ImplicitRepresentation.owns xml_boolean, lod3ImplicitRepresentation.ImplicitGeometry.gml_id xml_buffer, lod3ImplicitRepresentation.ImplicitGeometry.transformationMatrix xml_buffer, lod3ImplicitRepresentation.ImplicitGeometry.mimeType xml_buffer, lod3ImplicitRepresentation.ImplicitGeometry.mimeType.codeSpace xml_buffer, lod3ImplicitRepresentation.ImplicitGeometry.libraryObject xml_buffer, lod3ImplicitRepresentation.ImplicitGeometry.referencePoint xml_geometry, lod3ImplicitRepresentation.ImplicitGeometry.relativeGeometry xml_geometry, lod3ImplicitRepresentation.ImplicitGeometry.appearance{}.nilReason xml_buffer,
      lod3ImplicitRepresentation.ImplicitGeometry.appearance{}.gml_remoteSchema xml_buffer, lod3ImplicitRepresentation.ImplicitGeometry.appearance{}.xlink_href xml_buffer, lod3ImplicitRepresentation.ImplicitGeometry.appearance{}.xlink_role xml_buffer, lod3ImplicitRepresentation.ImplicitGeometry.appearance{}.xlink_title xml_buffer, lod3ImplicitRepresentation.ImplicitGeometry.appearance{}.owns xml_boolean, adeOfAbstractOccupiedSpace{} xml_xml, class xml_buffer, class.codeSpace xml_buffer, function{} xml_buffer, function{}.codeSpace xml_buffer, usage{} xml_buffer, usage{}.codeSpace xml_buffer, adeOfGenericOccupiedSpace{} xml_xml
Building (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, lod1TerrainIntersectionCurve xml_geometry, lod2TerrainIntersectionCurve xml_geometry,
      lod3TerrainIntersectionCurve xml_geometry, pointCloud.nilReason xml_buffer, pointCloud.gml_remoteSchema xml_buffer, pointCloud.xlink_href xml_buffer, pointCloud.xlink_role xml_buffer, pointCloud.xlink_title xml_buffer, pointCloud.owns xml_boolean, adeOfAbstractPhysicalSpace{} xml_xml, lod1ImplicitRepresentation.nilReason xml_buffer, lod1ImplicitRepresentation.gml_remoteSchema xml_buffer, lod1ImplicitRepresentation.xlink_href xml_buffer, lod1ImplicitRepresentation.xlink_role xml_buffer, lod1ImplicitRepresentation.xlink_title xml_buffer, lod1ImplicitRepresentation.owns xml_boolean, lod1ImplicitRepresentation.ImplicitGeometry.gml_id xml_buffer, lod1ImplicitRepresentation.ImplicitGeometry.transformationMatrix xml_buffer, lod1ImplicitRepresentation.ImplicitGeometry.mimeType xml_buffer, lod1ImplicitRepresentation.ImplicitGeometry.mimeType.codeSpace xml_buffer, lod1ImplicitRepresentation.ImplicitGeometry.libraryObject xml_buffer, lod1ImplicitRepresentation.ImplicitGeometry.referencePoint xml_geometry, lod1ImplicitRepresentation.ImplicitGeometry.relativeGeometry xml_geometry, lod1ImplicitRepresentation.ImplicitGeometry.appearance{}.nilReason xml_buffer, lod1ImplicitRepresentation.ImplicitGeometry.appearance{}.gml_remoteSchema xml_buffer, lod1ImplicitRepresentation.ImplicitGeometry.appearance{}.xlink_href xml_buffer, lod1ImplicitRepresentation.ImplicitGeometry.appearance{}.xlink_role xml_buffer, lod1ImplicitRepresentation.ImplicitGeometry.appearance{}.xlink_title xml_buffer, lod1ImplicitRepresentation.ImplicitGeometry.appearance{}.owns xml_boolean, lod2ImplicitRepresentation.nilReason xml_buffer, lod2ImplicitRepresentation.gml_remoteSchema xml_buffer, lod2ImplicitRepresentation.xlink_href xml_buffer,
      lod2ImplicitRepresentation.xlink_role xml_buffer, lod2ImplicitRepresentation.xlink_title xml_buffer, lod2ImplicitRepresentation.owns xml_boolean, lod2ImplicitRepresentation.ImplicitGeometry.gml_id xml_buffer, lod2ImplicitRepresentation.ImplicitGeometry.transformationMatrix xml_buffer, lod2ImplicitRepresentation.ImplicitGeometry.mimeType xml_buffer, lod2ImplicitRepresentation.ImplicitGeometry.mimeType.codeSpace xml_buffer, lod2ImplicitRepresentation.ImplicitGeometry.libraryObject xml_buffer, lod2ImplicitRepresentation.ImplicitGeometry.referencePoint xml_geometry, lod2ImplicitRepresentation.ImplicitGeometry.relativeGeometry xml_geometry, lod2ImplicitRepresentation.ImplicitGeometry.appearance{}.nilReason xml_buffer, lod2ImplicitRepresentation.ImplicitGeometry.appearance{}.gml_remoteSchema xml_buffer, lod2ImplicitRepresentation.ImplicitGeometry.appearance{}.xlink_href xml_buffer, lod2ImplicitRepresentation.ImplicitGeometry.appearance{}.xlink_role xml_buffer, lod2ImplicitRepresentation.ImplicitGeometry.appearance{}.xlink_title xml_buffer, lod2ImplicitRepresentation.ImplicitGeometry.appearance{}.owns xml_boolean, lod3ImplicitRepresentation.nilReason xml_buffer, lod3ImplicitRepresentation.gml_remoteSchema xml_buffer, lod3ImplicitRepresentation.xlink_href xml_buffer, lod3ImplicitRepresentation.xlink_role xml_buffer, lod3ImplicitRepresentation.xlink_title xml_buffer, lod3ImplicitRepresentation.owns xml_boolean, lod3ImplicitRepresentation.ImplicitGeometry.gml_id xml_buffer, lod3ImplicitRepresentation.ImplicitGeometry.transformationMatrix xml_buffer, lod3ImplicitRepresentation.ImplicitGeometry.mimeType xml_buffer, lod3ImplicitRepresentation.ImplicitGeometry.mimeType.codeSpace xml_buffer, lod3ImplicitRepresentation.ImplicitGeometry.libraryObject xml_buffer, lod3ImplicitRepresentation.ImplicitGeometry.referencePoint xml_geometry, lod3ImplicitRepresentation.ImplicitGeometry.relativeGeometry xml_geometry, lod3ImplicitRepresentation.ImplicitGeometry.appearance{}.nilReason xml_buffer,
      lod3ImplicitRepresentation.ImplicitGeometry.appearance{}.gml_remoteSchema xml_buffer, lod3ImplicitRepresentation.ImplicitGeometry.appearance{}.xlink_href xml_buffer, lod3ImplicitRepresentation.ImplicitGeometry.appearance{}.xlink_role xml_buffer, lod3ImplicitRepresentation.ImplicitGeometry.appearance{}.xlink_title xml_buffer, lod3ImplicitRepresentation.ImplicitGeometry.appearance{}.owns xml_boolean, adeOfAbstractOccupiedSpace{} xml_xml, conditionOfConstruction xml_char(17), dateOfConstruction xml_date, dateOfDemolition xml_date, constructionEvent{}.ConstructionEvent.event xml_buffer, constructionEvent{}.ConstructionEvent.event.codeSpace xml_buffer, constructionEvent{}.ConstructionEvent.dateOfEvent xml_date, constructionEvent{}.ConstructionEvent.description xml_buffer, elevation{}.Elevation.elevationReference xml_buffer, elevation{}.Elevation.elevationReference.codeSpace xml_buffer, elevation{}.Elevation.elevationValue xml_buffer, elevation{}.Elevation.elevationValue.srsName xml_buffer, elevation{}.Elevation.elevationValue.srsDimension xml_uint64, elevation{}.Elevation.elevationValue.axisLabels xml_buffer, elevation{}.Elevation.elevationValue.uomLabels xml_buffer, height{}.Height.highReference xml_buffer, height{}.Height.highReference.codeSpace xml_buffer, height{}.Height.lowReference xml_buffer, height{}.Height.lowReference.codeSpace xml_buffer, height{}.Height.status xml_char(9), height{}.Height.value xml_real64, height{}.Height.value.uom xml_buffer, occupancy{}.Occupancy.numberOfOccupants xml_int64, occupancy{}.Occupancy.interval xml_buffer, occupancy{}.Occupancy.interval.codeSpace xml_buffer,
      occupancy{}.Occupancy.occupantType xml_buffer, occupancy{}.Occupancy.occupantType.codeSpace xml_buffer, adeOfAbstractConstruction{} xml_xml, class xml_buffer, class.codeSpace xml_buffer, function{} xml_buffer, function{}.codeSpace xml_buffer, usage{} xml_buffer, usage{}.codeSpace xml_buffer, roofType xml_buffer, roofType.codeSpace xml_buffer, storeysAboveGround xml_int64, storeysBelowGround xml_int64, storeyHeightsAboveGround xml_buffer, storeyHeightsAboveGround.uom xml_buffer, storeyHeightsBelowGround xml_buffer, storeyHeightsBelowGround.uom xml_buffer, buildingConstructiveElement{}.nilReason xml_buffer, buildingConstructiveElement{}.gml_remoteSchema xml_buffer, buildingConstructiveElement{}.xlink_href xml_buffer, buildingConstructiveElement{}.xlink_role xml_buffer, buildingConstructiveElement{}.xlink_title xml_buffer, buildingConstructiveElement{}.owns xml_boolean, buildingInstallation{}.nilReason xml_buffer, buildingInstallation{}.gml_remoteSchema xml_buffer, buildingInstallation{}.xlink_href xml_buffer, buildingInstallation{}.xlink_role xml_buffer, buildingInstallation{}.xlink_title xml_buffer, buildingInstallation{}.owns xml_boolean, buildingRoom{}.nilReason xml_buffer,
      buildingRoom{}.gml_remoteSchema xml_buffer, buildingRoom{}.xlink_href xml_buffer, buildingRoom{}.xlink_role xml_buffer, buildingRoom{}.xlink_title xml_buffer, buildingRoom{}.owns xml_boolean, buildingFurniture{}.nilReason xml_buffer, buildingFurniture{}.gml_remoteSchema xml_buffer, buildingFurniture{}.xlink_href xml_buffer, buildingFurniture{}.xlink_role xml_buffer, buildingFurniture{}.xlink_title xml_buffer, buildingFurniture{}.owns xml_boolean, buildingSubdivision{}.nilReason xml_buffer, buildingSubdivision{}.gml_remoteSchema xml_buffer, buildingSubdivision{}.xlink_href xml_buffer, buildingSubdivision{}.xlink_role xml_buffer, buildingSubdivision{}.xlink_title xml_buffer, buildingSubdivision{}.owns xml_boolean, address{}.nilReason xml_buffer, address{}.gml_remoteSchema xml_buffer, address{}.xlink_href xml_buffer, address{}.xlink_role xml_buffer, address{}.xlink_title xml_buffer, address{}.owns xml_boolean, adeOfAbstractBuilding{} xml_xml, buildingPart{}.nilReason xml_buffer, buildingPart{}.gml_remoteSchema xml_buffer, buildingPart{}.xlink_href xml_buffer, buildingPart{}.xlink_role xml_buffer, buildingPart{}.xlink_title xml_buffer, buildingPart{}.owns xml_boolean,
      adeOfBuilding{} xml_xml
Tunnel (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, lod1TerrainIntersectionCurve xml_geometry, lod2TerrainIntersectionCurve xml_geometry,
      lod3TerrainIntersectionCurve xml_geometry, pointCloud.nilReason xml_buffer, pointCloud.gml_remoteSchema xml_buffer, pointCloud.xlink_href xml_buffer, pointCloud.xlink_role xml_buffer, pointCloud.xlink_title xml_buffer, pointCloud.owns xml_boolean, adeOfAbstractPhysicalSpace{} xml_xml, lod1ImplicitRepresentation.nilReason xml_buffer, lod1ImplicitRepresentation.gml_remoteSchema xml_buffer, lod1ImplicitRepresentation.xlink_href xml_buffer, lod1ImplicitRepresentation.xlink_role xml_buffer, lod1ImplicitRepresentation.xlink_title xml_buffer, lod1ImplicitRepresentation.owns xml_boolean, lod1ImplicitRepresentation.ImplicitGeometry.gml_id xml_buffer, lod1ImplicitRepresentation.ImplicitGeometry.transformationMatrix xml_buffer, lod1ImplicitRepresentation.ImplicitGeometry.mimeType xml_buffer, lod1ImplicitRepresentation.ImplicitGeometry.mimeType.codeSpace xml_buffer, lod1ImplicitRepresentation.ImplicitGeometry.libraryObject xml_buffer, lod1ImplicitRepresentation.ImplicitGeometry.referencePoint xml_geometry, lod1ImplicitRepresentation.ImplicitGeometry.relativeGeometry xml_geometry, lod1ImplicitRepresentation.ImplicitGeometry.appearance{}.nilReason xml_buffer, lod1ImplicitRepresentation.ImplicitGeometry.appearance{}.gml_remoteSchema xml_buffer, lod1ImplicitRepresentation.ImplicitGeometry.appearance{}.xlink_href xml_buffer, lod1ImplicitRepresentation.ImplicitGeometry.appearance{}.xlink_role xml_buffer, lod1ImplicitRepresentation.ImplicitGeometry.appearance{}.xlink_title xml_buffer, lod1ImplicitRepresentation.ImplicitGeometry.appearance{}.owns xml_boolean, lod2ImplicitRepresentation.nilReason xml_buffer, lod2ImplicitRepresentation.gml_remoteSchema xml_buffer, lod2ImplicitRepresentation.xlink_href xml_buffer,
      lod2ImplicitRepresentation.xlink_role xml_buffer, lod2ImplicitRepresentation.xlink_title xml_buffer, lod2ImplicitRepresentation.owns xml_boolean, lod2ImplicitRepresentation.ImplicitGeometry.gml_id xml_buffer, lod2ImplicitRepresentation.ImplicitGeometry.transformationMatrix xml_buffer, lod2ImplicitRepresentation.ImplicitGeometry.mimeType xml_buffer, lod2ImplicitRepresentation.ImplicitGeometry.mimeType.codeSpace xml_buffer, lod2ImplicitRepresentation.ImplicitGeometry.libraryObject xml_buffer, lod2ImplicitRepresentation.ImplicitGeometry.referencePoint xml_geometry, lod2ImplicitRepresentation.ImplicitGeometry.relativeGeometry xml_geometry, lod2ImplicitRepresentation.ImplicitGeometry.appearance{}.nilReason xml_buffer, lod2ImplicitRepresentation.ImplicitGeometry.appearance{}.gml_remoteSchema xml_buffer, lod2ImplicitRepresentation.ImplicitGeometry.appearance{}.xlink_href xml_buffer, lod2ImplicitRepresentation.ImplicitGeometry.appearance{}.xlink_role xml_buffer, lod2ImplicitRepresentation.ImplicitGeometry.appearance{}.xlink_title xml_buffer, lod2ImplicitRepresentation.ImplicitGeometry.appearance{}.owns xml_boolean, lod3ImplicitRepresentation.nilReason xml_buffer, lod3ImplicitRepresentation.gml_remoteSchema xml_buffer, lod3ImplicitRepresentation.xlink_href xml_buffer, lod3ImplicitRepresentation.xlink_role xml_buffer, lod3ImplicitRepresentation.xlink_title xml_buffer, lod3ImplicitRepresentation.owns xml_boolean, lod3ImplicitRepresentation.ImplicitGeometry.gml_id xml_buffer, lod3ImplicitRepresentation.ImplicitGeometry.transformationMatrix xml_buffer, lod3ImplicitRepresentation.ImplicitGeometry.mimeType xml_buffer, lod3ImplicitRepresentation.ImplicitGeometry.mimeType.codeSpace xml_buffer, lod3ImplicitRepresentation.ImplicitGeometry.libraryObject xml_buffer, lod3ImplicitRepresentation.ImplicitGeometry.referencePoint xml_geometry, lod3ImplicitRepresentation.ImplicitGeometry.relativeGeometry xml_geometry, lod3ImplicitRepresentation.ImplicitGeometry.appearance{}.nilReason xml_buffer,
      lod3ImplicitRepresentation.ImplicitGeometry.appearance{}.gml_remoteSchema xml_buffer, lod3ImplicitRepresentation.ImplicitGeometry.appearance{}.xlink_href xml_buffer, lod3ImplicitRepresentation.ImplicitGeometry.appearance{}.xlink_role xml_buffer, lod3ImplicitRepresentation.ImplicitGeometry.appearance{}.xlink_title xml_buffer, lod3ImplicitRepresentation.ImplicitGeometry.appearance{}.owns xml_boolean, adeOfAbstractOccupiedSpace{} xml_xml, conditionOfConstruction xml_char(17), dateOfConstruction xml_date, dateOfDemolition xml_date, constructionEvent{}.ConstructionEvent.event xml_buffer, constructionEvent{}.ConstructionEvent.event.codeSpace xml_buffer, constructionEvent{}.ConstructionEvent.dateOfEvent xml_date, constructionEvent{}.ConstructionEvent.description xml_buffer, elevation{}.Elevation.elevationReference xml_buffer, elevation{}.Elevation.elevationReference.codeSpace xml_buffer, elevation{}.Elevation.elevationValue xml_buffer, elevation{}.Elevation.elevationValue.srsName xml_buffer, elevation{}.Elevation.elevationValue.srsDimension xml_uint64, elevation{}.Elevation.elevationValue.axisLabels xml_buffer, elevation{}.Elevation.elevationValue.uomLabels xml_buffer, height{}.Height.highReference xml_buffer, height{}.Height.highReference.codeSpace xml_buffer, height{}.Height.lowReference xml_buffer, height{}.Height.lowReference.codeSpace xml_buffer, height{}.Height.status xml_char(9), height{}.Height.value xml_real64, height{}.Height.value.uom xml_buffer, occupancy{}.Occupancy.numberOfOccupants xml_int64, occupancy{}.Occupancy.interval xml_buffer, occupancy{}.Occupancy.interval.codeSpace xml_buffer,
      occupancy{}.Occupancy.occupantType xml_buffer, occupancy{}.Occupancy.occupantType.codeSpace xml_buffer, adeOfAbstractConstruction{} xml_xml, class xml_buffer, class.codeSpace xml_buffer, function{} xml_buffer, function{}.codeSpace xml_buffer, usage{} xml_buffer, usage{}.codeSpace xml_buffer, tunnelConstructiveElement{}.nilReason xml_buffer, tunnelConstructiveElement{}.gml_remoteSchema xml_buffer, tunnelConstructiveElement{}.xlink_href xml_buffer, tunnelConstructiveElement{}.xlink_role xml_buffer, tunnelConstructiveElement{}.xlink_title xml_buffer, tunnelConstructiveElement{}.owns xml_boolean, tunnelInstallation{}.nilReason xml_buffer, tunnelInstallation{}.gml_remoteSchema xml_buffer, tunnelInstallation{}.xlink_href xml_buffer, tunnelInstallation{}.xlink_role xml_buffer, tunnelInstallation{}.xlink_title xml_buffer, tunnelInstallation{}.owns xml_boolean, hollowSpace{}.nilReason xml_buffer, hollowSpace{}.gml_remoteSchema xml_buffer, hollowSpace{}.xlink_href xml_buffer, hollowSpace{}.xlink_role xml_buffer, hollowSpace{}.xlink_title xml_buffer, hollowSpace{}.owns xml_boolean, tunnelFurniture{}.nilReason xml_buffer, tunnelFurniture{}.gml_remoteSchema xml_buffer, tunnelFurniture{}.xlink_href xml_buffer,
      tunnelFurniture{}.xlink_role xml_buffer, tunnelFurniture{}.xlink_title xml_buffer, tunnelFurniture{}.owns xml_boolean, adeOfAbstractTunnel{} xml_xml, tunnelPart{}.nilReason xml_buffer, tunnelPart{}.gml_remoteSchema xml_buffer, tunnelPart{}.xlink_href xml_buffer, tunnelPart{}.xlink_role xml_buffer, tunnelPart{}.xlink_title xml_buffer, tunnelPart{}.owns xml_boolean, adeOfTunnel{} xml_xml
Road (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, lod1TerrainIntersectionCurve xml_geometry, lod2TerrainIntersectionCurve xml_geometry,
      lod3TerrainIntersectionCurve xml_geometry, pointCloud.nilReason xml_buffer, pointCloud.gml_remoteSchema xml_buffer, pointCloud.xlink_href xml_buffer, pointCloud.xlink_role xml_buffer, pointCloud.xlink_title xml_buffer, pointCloud.owns xml_boolean, adeOfAbstractPhysicalSpace{} xml_xml, adeOfAbstractUnoccupiedSpace{} xml_xml, trafficDirection xml_char(9), occupancy{}.Occupancy.numberOfOccupants xml_int64, occupancy{}.Occupancy.interval xml_buffer, occupancy{}.Occupancy.interval.codeSpace xml_buffer, occupancy{}.Occupancy.occupantType xml_buffer, occupancy{}.Occupancy.occupantType.codeSpace xml_buffer, trafficSpace{}.nilReason xml_buffer, trafficSpace{}.gml_remoteSchema xml_buffer, trafficSpace{}.xlink_href xml_buffer, trafficSpace{}.xlink_role xml_buffer, trafficSpace{}.xlink_title xml_buffer, trafficSpace{}.owns xml_boolean, auxiliaryTrafficSpace{}.nilReason xml_buffer, auxiliaryTrafficSpace{}.gml_remoteSchema xml_buffer, auxiliaryTrafficSpace{}.xlink_href xml_buffer, auxiliaryTrafficSpace{}.xlink_role xml_buffer, auxiliaryTrafficSpace{}.xlink_title xml_buffer, auxiliaryTrafficSpace{}.owns xml_boolean, hole{}.nilReason xml_buffer, hole{}.gml_remoteSchema xml_buffer, hole{}.xlink_href xml_buffer,
      hole{}.xlink_role xml_buffer, hole{}.xlink_title xml_buffer, hole{}.owns xml_boolean, marking{}.nilReason xml_buffer, marking{}.gml_remoteSchema xml_buffer, marking{}.xlink_href xml_buffer, marking{}.xlink_role xml_buffer, marking{}.xlink_title xml_buffer, marking{}.owns xml_boolean, adeOfAbstractTransportationSpace{} xml_xml, class xml_buffer, class.codeSpace xml_buffer, function{} xml_buffer, function{}.codeSpace xml_buffer, usage{} xml_buffer, usage{}.codeSpace xml_buffer, section{}.nilReason xml_buffer, section{}.gml_remoteSchema xml_buffer, section{}.xlink_href xml_buffer, section{}.xlink_role xml_buffer, section{}.xlink_title xml_buffer, section{}.owns xml_boolean, intersection{}.nilReason xml_buffer, intersection{}.gml_remoteSchema xml_buffer, intersection{}.xlink_href xml_buffer, intersection{}.xlink_role xml_buffer, intersection{}.xlink_title xml_buffer, intersection{}.owns xml_boolean, adeOfRoad{} xml_xml
AttributeFilter
    ATTR_NAME = LegalSpace
    ATTR_VALUES = <Empty>,<Missing>,<Null>,<Unfiltered>,Lot,Easement,DepthLimitation,CommonProperty,CrownAllotment
    Lot -> Lot (writer GML_1)
    Easement -> Easement (writer GML_1)
    DepthLimitation -> DepthLimitation (writer GML_1)
    CommonProperty -> CommonProperty (writer GML_1)
    CrownAllotment -> CrownAllotment (writer GML_1)
Lot (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, adeOfAbstractLogicalSpace{} xml_xml, class xml_buffer,
      class.codeSpace xml_buffer, function{} xml_buffer, function{}.codeSpace xml_buffer, usage{} xml_buffer, usage{}.codeSpace xml_buffer, groupMember{}.owns xml_boolean, groupMember{}.Role.gml_id xml_buffer, groupMember{}.Role.role xml_buffer, groupMember{}.Role.groupMember.nilReason xml_buffer, groupMember{}.Role.groupMember.gml_remoteSchema xml_buffer, groupMember{}.Role.groupMember.xlink_href xml_buffer, groupMember{}.Role.groupMember.xlink_role xml_buffer, groupMember{}.Role.groupMember.xlink_title xml_buffer, groupMember{}.Role.groupMember.owns xml_boolean, parent.owns xml_boolean, parent.nilReason xml_buffer, parent.gml_remoteSchema xml_buffer, parent.xlink_href xml_buffer, parent.xlink_role xml_buffer, parent.xlink_title xml_buffer, adeOfCityObjectGroup{} xml_xml, parcelType xml_char(9), parcelState xml_char(12), parcelDimension xml_char(2), parcelUse xml_buffer, parcelTitleType xml_char(17), parcelName xml_buffer, affectedBy{}.nilReason xml_buffer, affectedBy{}.gml_remoteSchema xml_buffer, affectedBy{}.xlink_href xml_buffer,
      affectedBy{}.xlink_role xml_buffer, affectedBy{}.xlink_title xml_buffer, affectedBy{}.owns xml_boolean, entitlement xml_real64, liability xml_real64, titleRefVol xml_int64, owner xml_buffer, titleRefFol xml_int64, address.nilReason xml_buffer, address.gml_remoteSchema xml_buffer, address.xlink_href xml_buffer, address.xlink_role xml_buffer, address.xlink_title xml_buffer, address.owns xml_boolean
Easement (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, adeOfAbstractLogicalSpace{} xml_xml, class xml_buffer,
      class.codeSpace xml_buffer, function{} xml_buffer, function{}.codeSpace xml_buffer, usage{} xml_buffer, usage{}.codeSpace xml_buffer, groupMember{}.owns xml_boolean, groupMember{}.Role.gml_id xml_buffer, groupMember{}.Role.role xml_buffer, groupMember{}.Role.groupMember.nilReason xml_buffer, groupMember{}.Role.groupMember.gml_remoteSchema xml_buffer, groupMember{}.Role.groupMember.xlink_href xml_buffer, groupMember{}.Role.groupMember.xlink_role xml_buffer, groupMember{}.Role.groupMember.xlink_title xml_buffer, groupMember{}.Role.groupMember.owns xml_boolean, parent.owns xml_boolean, parent.nilReason xml_buffer, parent.gml_remoteSchema xml_buffer, parent.xlink_href xml_buffer, parent.xlink_role xml_buffer, parent.xlink_title xml_buffer, adeOfCityObjectGroup{} xml_xml, parcelType xml_char(9), parcelState xml_char(12), parcelDimension xml_char(2), parcelUse xml_buffer, parcelTitleType xml_char(17), parcelName xml_buffer, fixedBy{}.nilReason xml_buffer, fixedBy{}.gml_remoteSchema xml_buffer, fixedBy{}.xlink_href xml_buffer,
      fixedBy{}.xlink_role xml_buffer, fixedBy{}.xlink_title xml_buffer, fixedBy{}.owns xml_boolean, easementType xml_char(16), origin xml_buffer, beneficiary xml_buffer, width xml_real64
DepthLimitation (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, adeOfAbstractLogicalSpace{} xml_xml, class xml_buffer,
      class.codeSpace xml_buffer, function{} xml_buffer, function{}.codeSpace xml_buffer, usage{} xml_buffer, usage{}.codeSpace xml_buffer, groupMember{}.owns xml_boolean, groupMember{}.Role.gml_id xml_buffer, groupMember{}.Role.role xml_buffer, groupMember{}.Role.groupMember.nilReason xml_buffer, groupMember{}.Role.groupMember.gml_remoteSchema xml_buffer, groupMember{}.Role.groupMember.xlink_href xml_buffer, groupMember{}.Role.groupMember.xlink_role xml_buffer, groupMember{}.Role.groupMember.xlink_title xml_buffer, groupMember{}.Role.groupMember.owns xml_boolean, parent.owns xml_boolean, parent.nilReason xml_buffer, parent.gml_remoteSchema xml_buffer, parent.xlink_href xml_buffer, parent.xlink_role xml_buffer, parent.xlink_title xml_buffer, adeOfCityObjectGroup{} xml_xml, parcelType xml_char(9), parcelState xml_char(12), parcelDimension xml_char(2), parcelUse xml_buffer, parcelTitleType xml_char(17), parcelName xml_buffer, fixedBy{}.nilReason xml_buffer, fixedBy{}.gml_remoteSchema xml_buffer, fixedBy{}.xlink_href xml_buffer,
      fixedBy{}.xlink_role xml_buffer, fixedBy{}.xlink_title xml_buffer, fixedBy{}.owns xml_boolean, landApplied xml_buffer, length xml_real64, upperLimit xml_real64, lowerLimit xml_real64
CommonProperty (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, adeOfAbstractLogicalSpace{} xml_xml, class xml_buffer,
      class.codeSpace xml_buffer, function{} xml_buffer, function{}.codeSpace xml_buffer, usage{} xml_buffer, usage{}.codeSpace xml_buffer, groupMember{}.owns xml_boolean, groupMember{}.Role.gml_id xml_buffer, groupMember{}.Role.role xml_buffer, groupMember{}.Role.groupMember.nilReason xml_buffer, groupMember{}.Role.groupMember.gml_remoteSchema xml_buffer, groupMember{}.Role.groupMember.xlink_href xml_buffer, groupMember{}.Role.groupMember.xlink_role xml_buffer, groupMember{}.Role.groupMember.xlink_title xml_buffer, groupMember{}.Role.groupMember.owns xml_boolean, parent.owns xml_boolean, parent.nilReason xml_buffer, parent.gml_remoteSchema xml_buffer, parent.xlink_href xml_buffer, parent.xlink_role xml_buffer, parent.xlink_title xml_buffer, adeOfCityObjectGroup{} xml_xml, parcelType xml_char(9), parcelState xml_char(12), parcelDimension xml_char(2), parcelUse xml_buffer, parcelTitleType xml_char(17), parcelName xml_buffer, affectedBy{}.nilReason xml_buffer, affectedBy{}.gml_remoteSchema xml_buffer, affectedBy{}.xlink_href xml_buffer,
      affectedBy{}.xlink_role xml_buffer, affectedBy{}.xlink_title xml_buffer, affectedBy{}.owns xml_boolean, limitationsOfOwnersCorporation xml_char(26), LandAffectedByOwnersCorporation{}.nilReason xml_buffer, LandAffectedByOwnersCorporation{}.gml_remoteSchema xml_buffer, LandAffectedByOwnersCorporation{}.xlink_href xml_buffer, LandAffectedByOwnersCorporation{}.xlink_role xml_buffer, LandAffectedByOwnersCorporation{}.xlink_title xml_buffer, LandAffectedByOwnersCorporation{}.owns xml_boolean
CrownAllotment (writer GML_1)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, adeOfAbstractLogicalSpace{} xml_xml, class xml_buffer,
      class.codeSpace xml_buffer, function{} xml_buffer, function{}.codeSpace xml_buffer, usage{} xml_buffer, usage{}.codeSpace xml_buffer, groupMember{}.owns xml_boolean, groupMember{}.Role.gml_id xml_buffer, groupMember{}.Role.role xml_buffer, groupMember{}.Role.groupMember.nilReason xml_buffer, groupMember{}.Role.groupMember.gml_remoteSchema xml_buffer, groupMember{}.Role.groupMember.xlink_href xml_buffer, groupMember{}.Role.groupMember.xlink_role xml_buffer, groupMember{}.Role.groupMember.xlink_title xml_buffer, groupMember{}.Role.groupMember.owns xml_boolean, parent.owns xml_boolean, parent.nilReason xml_buffer, parent.gml_remoteSchema xml_buffer, parent.xlink_href xml_buffer, parent.xlink_role xml_buffer, parent.xlink_title xml_buffer, adeOfCityObjectGroup{} xml_xml, parcelType xml_char(9), parcelState xml_char(12), parcelDimension xml_char(2), parcelUse xml_buffer, parcelTitleType xml_char(17), parcelName xml_buffer, affectedBy{}.nilReason xml_buffer, affectedBy{}.gml_remoteSchema xml_buffer, affectedBy{}.xlink_href xml_buffer,
      affectedBy{}.xlink_role xml_buffer, affectedBy{}.xlink_title xml_buffer, affectedBy{}.owns xml_boolean
StageLot (writer GML_1)
    attributes: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
Reserve (writer GML_1)
    attributes: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
Restriction (writer GML_1)
    attributes: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
CrownPortion (writer GML_1)
    attributes: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
